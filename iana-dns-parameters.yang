module iana-dns-parameters {

  yang-version "1.1";

  namespace "http://www.nic.cz/ns/yang/iana-dns-parameters";

  prefix "ianadns";

  organization
    "CZ.NIC, z. s. p. o.";

  contact
    "Editor:   Ladislav Lhotka
               <mailto:lhotka@nic.cz>";

  description
    "This module provides several data types that are maintained in
     IANA registries related to DNS resource records.";

  reference
    "- IANA: Domain Name System (DNS) Parameters.
       http://www.iana.org/assignments/dns-parameters/dns-parameters.xhtml

     - IANA: Domain Name System Security (DNSSEC) Algorithm Numbers.
       http://www.iana.org/assignments/dns-sec-alg-numbers/dns-sec-alg-numbers.xhtml

     - IANA: Delegation Signer (DS) Resource Record (RR) Type Digest
       Algorithms.
       http://www.iana.org/assignments/ds-rr-types/ds-rr-types.xhtml#ds-rr-types-1

     - IANA: Domain Name System Security (DNSSEC) NextSECure3 (NSEC3)
       Parameters.
       https://www.iana.org/assignments/dnssec-nsec3-parameters/dnssec-nsec3-parameters.xhtml

     - IANA: DNSKEY Flags.
       https://www.iana.org/assignments/dnskey-flags/dnskey-flags.xhtml

     - IANA: DNS-Based Authentication of Named Entities (DANE)
       Parameters.
       http://www.iana.org/assignments/dane-parameters/dane-parameters.xhtml

     - IANA: IPSECKEY Resource Record Parameters.
       https://www.iana.org/assignments/ipseckey-rr-parameters/ipseckey-rr-parameters.xhtml

     - IANA: DNS SSHFP Resource Record Parameters.
       https://www.iana.org/assignments/dns-sshfp-rr-parameters/dns-sshfp-rr-parameters.xhtml";

  revision 2015-08-11 {
    description
      "Initial revision.";
  }

  /* Typedefs */

  typedef class {
    type enumeration {
      enum IN {
        value "1";
        description
          "Internet";
      }
      enum CH {
        value "3";
        description
          "Chaos";
      }
      enum HS {
        value "4";
        description
          "Hesiod";
      }
      enum NONE {
        value "254";
        description
          "QCLASS NONE - only meaningful in queries";
      }
      enum ANY {
        value "255";
        description
          "QCLASS * (ANY) - only meaningful in queries";
      }
    }
    description
      "This enumeration type defines DNS resource record classes.";
    reference
      "- RFC 1035: Domain Names - Implementation and Specification

       - RFC 2136: Dynamic Updates in the Domain Name System (DNS
         UPDATE)";
  }

  typedef dnssec-algorithm {
    type enumeration {
      enum RSAMD5 {
        value "1";
        status "deprecated";
        description
          "RSA/MD5";
      }
      enum DH {
        value "2";
        description
          "Diffie-Hellman";
      }
      enum DSA {
        value "3";
        description
          "DSA/SHA1";
      }
      enum RSASHA1 {
        value "5";
        description
          "RSA/SHA1";
      }
      enum DSA-NSEC3-SHA1 {
        value "6";
        description
          "DSA-NSEC3-SHA1";
      }
      enum RSASHA1-NSEC3-SHA1 {
        value "7";
        description
          "RSASHA1-NSEC3-SHA1";
      }
      enum RSASHA256 {
        value "8";
        description
          "RSA/SHA256";
      }
      enum RSASHA512 {
        value "10";
        description
          "RSA/SHA512";
      }
      enum ECC-GOST {
        value "12";
        description
          "GOST R 34.10-2001";
      }
      enum ECDSAP256SHA256 {
        value "13";
        description
          "ECDSA Curve P-256 with SHA-256";
      }
      enum ECDSAP384SHA384 {
        value "14";
        description
          "ECDSA Curve P-384 with SHA-384";
      }
    }
    description
      "This enumeration type defines algorithms for DNSSEC signing as
       defined by IANA.

       The numbers defined by the 'value' statements are used in KEY,
       SIG, DNSKEY, RRSIG and CERT resource records for identifying
       the security algorithm.

       Value 0, 4, 9 and 11 are reserved.";
    reference
      "RFC 4034: Resource Records for the DNS Security Extensions";
  }

  typedef digest-algorithm {
    type enumeration {
      enum SHA-1 {
        value "1";
        description
          "SHA-1 digest algorithm. Mandatory to support.";
        reference
          "RFC 4034: Resource Records for the DNS Security
           Extensions";
      }
      enum SHA-256 {
        value "2";
        description
          "SHA-256 digest algorithm. Mandatory to support.";
        reference
          "RFC 4509: Use of SHA-256 in DNSSEC Delegation Signer (DS)
           Resource Records (RRs)";
      }
      enum GOST-R-34.11-94 {
        value "3";
        description
          "GOST R 34.11-94 digest algorithm. Optional to
           implement.";
        reference
          "RFC 5933: Use of GOST Signature Algorithms in DNSKEY and
           RRSIG Resource Records for DNSSEC";
      }
      enum SHA-384 {
        value "4";
        description
          "SHA-384 digest algorithm. Optional to support.";
        reference
          "RFC 6605: Elliptic Curve Digital Signature Algorithm (DSA)
           for DNSSEC";
      }
    }
    description
      "This enumeration type defines types of digest algorithms for
       Delegation Signer (DS) RR type.";
  }

  typedef dnskey-flags {
    type bits {
      bit ZONE {
        position "7";
        description
          "Zone Key flag.

           If this bit has value 1, then the DNSKEY record holds a
           DNS zone key. If bit 7 has value 0, then the DNSKEY record
           holds some other type of DNS public key and MUST NOT be
           used to verify RRSIGs that cover RRsets.";
      }
      bit REVOKE {
        position "8";
        description
          "Revoke flag.

           If this bit has value 1, and the resolver sees an
           RRSIG(DNSKEY) signed by the associated key, then the
           resolver MUST consider this key permanently invalid for
           all purposes except for validating the revocation.";
        reference
          "RFC 5011: Automated Updates of DNS Security (DNSSEC) Trust
           Anchors";
      }
      bit SEP {
        position "15";
        description
          "Secure Entry Point flag.

           If this bit has value 1, then the DNSKEY record holds a
           key intended for use as a secure entry point.";
        reference
          "RFC 3757: Domain Name System KEY (DNSKEY) Resource Record
           (RR) Secure Entry Point (SEP) Flag";
      }
    }
    description
      "This enumeration type defines flags for DNSKEY RR.";
    reference
      "RFC 4034: Resource Records for the DNS Security Extensions";
  }

  typedef dnssec-nsec3-flags {
    type bits {
      bit Opt-Out {
        position "7";
        description
          "The Opt-Out Flag indicates whether this NSEC3 resource
           record may cover unsigned delegations.";
      }
    }
    description
      "This enumeration type defines flags for NSEC3 RR.";
    reference
      "RFC 5155: DNS Security (DNSSEC) Hashed Authenticated Denial of
       Existence";
  }

  typedef dnssec-nsec3-hash-algorithm {
    type enumeration {
      enum SHA-1 {
        value "1";
        description
          "SHA-1 hash algorithm.";
      }
    }
    description
      "This enumeration type defines cryptographic hash algorithms
       used to construct the hash value in NSEC3 RR.";
    reference
      "RFC 5155: DNS Security (DNSSEC) Hashed Authenticated Denial of
       Existence";
  }

  typedef tlsa-certificate-usages {
    type enumeration {
      enum PKIX-TA {
        value "0";
        description
          "CA constraint.";
      }
      enum PKIX-EE {
        value "1";
        description
          "Service certificate constraint.";
      }
      enum DANE-TA {
        value "2";
        description
          "Trust anchor assertion.";
      }
      enum DANE-EE {
        value "3";
        description
          "Domain-issued certificate.";
      }
      enum PrivCert {
        value "255";
        description
          "Reserved for Private Use.";
      }
    }
    description
      "This enumeration type defines the provided association that
       will be used to match the certificate presented in the TLS
       handshake.";
    reference
      "RFC 6698: The DNS-Based Authentication of Named Entities
       (DANE) Transport Layer Security (TLS) Protocol: TLSA";
  }

  typedef tlsa-selectors {
    type enumeration {
      enum Cert {
        value "0";
        description
          "Full certificate.";
      }
      enum SPKI {
        value "1";
        description
          "SubjectPublicKeyInfo.";
      }
      enum PrivSel {
        value "255";
        description
          "Reserved for Private Use.";
      }
    }
    description
      "This enumeration type specifies which part of the TLS
       certificate presented by the server will be matched against
       the association data.";
    reference
      "RFC 6698: The DNS-Based Authentication of Named Entities
       (DANE) Transport Layer Security (TLS) Protocol: TLSA";
  }

  typedef tlsa-matching-type {
    type enumeration {
      enum Full {
        value "0";
        description
          "No hash used.";
      }
      enum SHA2-256 {
        value "1";
        description
          "256-bit hash by SHA2.";
        reference
          "RFC 6234: US Secure Hash Algorithms (SHA and SHA-based
           HMAC and HKDF)";
      }
      enum SHA2-512 {
        value "2";
        description
          "512-bit hash by SHA2.";
        reference
          "RFC 6234: US Secure Hash Algorithms (SHA and SHA-based
           HMAC and HKDF)";
      }
      enum PrivMatch {
        value "255";
        description
          "Reserved for Private Use.";
      }
    }
    description
      "This enumeration type specifies how the certificate
       association is presented.";
    reference
      "RFC 6698: The DNS-Based Authentication of Named Entities
       (DANE) Transport Layer Security (TLS) Protocol: TLSA";
  }

  typedef ipseckey-algorithm-type {
    type enumeration {
      enum no-key {
        value "0";
        description
          "No key is present.";
      }
      enum DSA {
        value "1";
        description
          "A DSA key is present, in the format defined in RFC
           2536.";
        reference
          "RFC 2536: DSA KEYs and SIGs in the Domain Name System
           (DNS)";
      }
      enum RSA {
        value "2";
        description
          "A RSA key is present, in the format defined in RFC
           3110.";
        reference
          "RFC 3110: RSA/SHA-1 SIGs and RSA KEYs in the Domain Name
           System (DNS)";
      }
    }
    description
      "This enumeration type specifies the IPSec public key's
       cryptographic algorithm.";
    reference
      "RFC 4025: A Method for Storing IPsec Keying Material in DNS";
  }

  typedef ipseckey-gateway-type {
    type enumeration {
      enum no-gateway {
        value "0";
        description
          "No gateway is present.";
      }
      enum IPv4-address {
        value "1";
        description
          "A 4-byte IPv4 address is present.";
      }
      enum IPv6-address {
        value "2";
        description
          "A 16-byte IPv6 address is present.";
      }
      enum domain-name {
        value "3";
        description
          "A wire-encoded domain name is present.";
      }
    }
    description
      "This enumeration type specifies the type of the gateway to
       which an IPsec tunnel may be created.";
    reference
      "RFC 4025: A Method for Storing IPsec Keying Material in DNS";
  }

  typedef sshfp-algorithm-type {
    type enumeration {
      enum RSA {
        value "1";
        description
          "RSA algorithm.";
      }
      enum DSA {
        value "2";
        description
          "DSA algorithm.";
      }
      enum ECDSA {
        value "3";
        description
          "ECDSA algorithm.";
        reference
          "RFC 6594: Use of the SHA-256 Algorithm with RSA, Digital
           Signature Algorithm (DSA), and Elliptic Curve DSA (ECDSA)
           in SSHFP Resource Records";
      }
      enum Ed25519 {
        value "4";
        description
          "Ed25519 algorithm.";
        reference
          "RFC 7479: Using Ed25519 in SSHFP Resource Records";
      }
    }
    description
      "This enumeration specifies the algorithm of the public key.";
    reference
      "RFC 4255: Using DNS to Securely Publish Secure Shell (SSH) Key
       Fingerprints";
  }

  typedef sshfp-fingerprint-type {
    type enumeration {
      enum SHA-1 {
        value "1";
        description
          "SHA-1 message-digest algorithm.";
      }
      enum SHA-256 {
        value "2";
        description
          "SHA-256 message-digest algorithm.";
        reference
          "RFC 6594: Use of the SHA-256 Algorithm with RSA, Digital
           Signature Algorithm (DSA), and Elliptic Curve DSA (ECDSA)
           in SSHFP Resource Records";
      }
    }
    description
      "This enumeration specifies the message-digest algorithm used
       to calculate the fingerprint of the public key.";
    reference
      "RFC 4255: Using DNS to Securely Publish Secure Shell (SSH) Key
       Fingerprints";
  }

  /* Identities */

  identity rrtype {
    description
      "Base identity from which DNS RRTYPEs are derived.";
  }

  identity data-rrtype {
    base ianadns:rrtype;
    description
      "Base identity from which data RRTYPEs are derived. These
       RRTYPEs are use for storing zone data.";
  }

  identity q-meta-rrtype {
    base ianadns:rrtype;
    description
      "Base identity from which special RRTYPEs are derived:

       - QTYPEs – used only in queries.

       - Meta-TYPEs – designate transient data associated with a
         particular DNS message and, in some cases, can also be used
         in queries.";
  }

  identity A {
    base ianadns:data-rrtype;
    description
      "A host address.

       Value of this RR is 1.";
    reference
      "RFC 1035";
  }

  identity NS {
    base ianadns:data-rrtype;
    description
      "An authoritative name server.

       Value of this RR is 2.";
    reference
      "RFC 1035";
  }

  identity MD {
    base ianadns:data-rrtype;
    status "obsolete";
    description
      "A mail destination (obsolete – use MX).

       Value of this RR is 3.";
    reference
      "RFC 1035";
  }

  identity MF {
    base ianadns:data-rrtype;
    status "obsolete";
    description
      "A mail forwarder (obsolete – use MX).

       Value of this RR is 4.";
    reference
      "RFC 1035";
  }

  identity CNAME {
    base ianadns:data-rrtype;
    description
      "The canonical name for an alias.

       Value of this RR is 5.";
    reference
      "RFC 1035";
  }

  identity SOA {
    base ianadns:data-rrtype;
    description
      "Marks the start of a zone of authority.

       Value of this RR is 6.";
    reference
      "RFC 1035";
  }

  identity MB {
    base ianadns:data-rrtype;
    description
      "A mailbox domain name (experimental).

       Value of this RR is 7.";
    reference
      "RFC 1035";
  }

  identity MG {
    base ianadns:data-rrtype;
    description
      "A mail group member (experimental).

       Value of this RR is 8.";
    reference
      "RFC 1035";
  }

  identity MR {
    base ianadns:data-rrtype;
    description
      "A mail rename domain name (experimental).

       Value of this RR is 9.";
    reference
      "RFC 1035";
  }

  identity NULL {
    base ianadns:data-rrtype;
    description
      "A null RR (experimental).

       Value of this RR is 10.";
    reference
      "RFC 1035";
  }

  identity WKS {
    base ianadns:data-rrtype;
    description
      "A well known service description.

       Value of this RR is 11.";
    reference
      "RFC 1035";
  }

  identity PTR {
    base ianadns:data-rrtype;
    description
      "A domain name pointer.

       Value of this RR is 12.";
    reference
      "RFC 1035";
  }

  identity HINFO {
    base ianadns:data-rrtype;
    description
      "Host information.

       Value of this RR is 13.";
    reference
      "RFC 1035";
  }

  identity MINFO {
    base ianadns:data-rrtype;
    description
      "Mailbox or mail list information.

       Value of this RR is 14.";
    reference
      "RFC 1035";
  }

  identity MX {
    base ianadns:data-rrtype;
    description
      "Mail exchange.

       Value of this RR is 15.";
    reference
      "RFC 1035";
  }

  identity TXT {
    base ianadns:data-rrtype;
    description
      "Text strings.

       Value of this RR is 16.";
    reference
      "RFC 1035";
  }

  identity RP {
    base ianadns:data-rrtype;
    description
      "Responsible Person.

       Value of this RR is 17.";
    reference
      "RFC 1183";
  }

  identity AFSDB {
    base ianadns:data-rrtype;
    description
      "Afs Data Base location.

       Value of this RR is 18.";
    reference
      "RFC 1183, RFC 5864";
  }

  identity X25 {
    base ianadns:data-rrtype;
    description
      "X.25 PSDN address.

       Value of this RR is 19.";
    reference
      "RFC 1183";
  }

  identity ISDN {
    base ianadns:data-rrtype;
    description
      "Isdn address.

       Value of this RR is 20.";
    reference
      "RFC 1183";
  }

  identity RT {
    base ianadns:data-rrtype;
    description
      "Route Through.

       Value of this RR is 21.";
    reference
      "RFC 1183";
  }

  identity NSAP {
    base ianadns:data-rrtype;
    description
      "Nsap address, NSAP style A record.

       Value of this RR is 22.";
    reference
      "RFC 1706";
  }

  identity NSAP-PTR {
    base ianadns:data-rrtype;
    description
      "Domain name pointer, NSAP style.

       Value of this RR is 23.";
    reference
      "RFC 1348, RFC 1637, RFC 1706";
  }

  identity SIG {
    base ianadns:data-rrtype;
    description
      "SEcurity signature.

       Value of this RR is 24.";
    reference
      "RFC 4034, RFC 3755, RFC 2535, RFC 2536, RFC 2537, RFC 2931,
       RFC 3110, RFC 3008";
  }

  identity KEY {
    base ianadns:data-rrtype;
    description
      "SeCurity key.

       Value of this RR is 25.";
    reference
      "RFC 4034, RFC 3755, RFC 2535, RFC 2536, RFC 2537, RFC 2539,
       RFC 3008, RFC 3110";
  }

  identity PX {
    base ianadns:data-rrtype;
    description
      "X.400 mail mapping information.

       Value of this RR is 26.";
    reference
      "RFC 2163";
  }

  identity GPOS {
    base ianadns:data-rrtype;
    description
      "Geographical Position.

       Value of this RR is 27.";
    reference
      "RFC 1712";
  }

  identity AAAA {
    base ianadns:data-rrtype;
    description
      "IPv6 Address.

       Value of this RR is 28.";
    reference
      "RFC 3596";
  }

  identity LOC {
    base ianadns:data-rrtype;
    description
      "Location Information.

       Value of this RR is 29.";
    reference
      "RFC 1876";
  }

  identity NXT {
    base ianadns:data-rrtype;
    status "obsolete";
    description
      "Next Domain (obsolete).

       Value of this RR is 30.";
    reference
      "RFC 3755, RFC 2535";
  }

  identity EID {
    base ianadns:data-rrtype;
    description
      "Endpoint Identifier.

       Value of this RR is 31.";
  }

  identity NIMLOC {
    base ianadns:data-rrtype;
    description
      "Nimrod Locator.

       Value of this RR is 32.";
  }

  identity SRV {
    base ianadns:data-rrtype;
    description
      "Server Selection.

       Value of this RR is 33.";
    reference
      "RFC 2782";
  }

  identity ATMA {
    base ianadns:data-rrtype;
    description
      "ATM Address.

       Value of this RR is 34.";
  }

  identity NAPTR {
    base ianadns:data-rrtype;
    description
      "Naming Authority Pointer.

       Value of this RR is 35.";
    reference
      "RFC 2915, RFC 2168, RFC 3403";
  }

  identity KX {
    base ianadns:data-rrtype;
    description
      "Key Exchanger.

       Value of this RR is 36.";
    reference
      "RFC 2230";
  }

  identity CERT {
    base ianadns:data-rrtype;
    description
      "CERT.

       Value of this RR is 37.";
    reference
      "RFC 4398";
  }

  identity A6 {
    base ianadns:data-rrtype;
    status "obsolete";
    description
      "A6 (obsolete – use AAAA).

       Value of this RR is 38.";
    reference
      "RFC 3226, RFC 2874, RFC 6563";
  }

  identity DNAME {
    base ianadns:data-rrtype;
    description
      "DNAME.

       Value of this RR is 39.";
    reference
      "RFC 6672";
  }

  identity SINK {
    base ianadns:data-rrtype;
    description
      "SINK.

       Value of this RR is 40.";
  }

  identity OPT {
    base ianadns:q-meta-rrtype;
    description
      "OPT.

       Value of this RR is 41.";
    reference
      "RFC 6891, RFC 3225";
  }

  identity APL {
    base ianadns:data-rrtype;
    description
      "APL.

       Value of this RR is 42.";
    reference
      "RFC 3123";
  }

  identity DS {
    base ianadns:data-rrtype;
    description
      "Delegation Signer.

       Value of this RR is 43.";
    reference
      "RFC 4034, RFC 3658";
  }

  identity SSHFP {
    base ianadns:data-rrtype;
    description
      "SSH Key Fingerprint.

       Value of this RR is 44.";
    reference
      "RFC 4255";
  }

  identity IPSECKEY {
    base ianadns:data-rrtype;
    description
      "IPSec key.

       Value of this RR is 45.";
    reference
      "RFC 4025";
  }

  identity RRSIG {
    base ianadns:data-rrtype;
    description
      "RR signature.

       Value of this RR is 46.";
    reference
      "RFC 4034, RFC 3755";
  }

  identity NSEC {
    base ianadns:data-rrtype;
    description
      "NSEC.

       Value of this RR is 47.";
    reference
      "RFC 4034, RFC 3755";
  }

  identity DNSKEY {
    base ianadns:data-rrtype;
    description
      "DNSKEY.

       Value of this RR is 48.";
    reference
      "RFC 4034, RFC 3755";
  }

  identity DHCID {
    base ianadns:data-rrtype;
    description
      "DHCID.

       Value of this RR is 49.";
    reference
      "RFC 4701";
  }

  identity NSEC3 {
    base ianadns:data-rrtype;
    description
      "NSEC3.

       Value of this RR is 50.";
    reference
      "RFC 5155";
  }

  identity NSEC3PARAM {
    base ianadns:data-rrtype;
    description
      "NSEC3PARAM.

       Value of this RR is 51.";
    reference
      "RFC 5155";
  }

  identity TLSA {
    base ianadns:data-rrtype;
    description
      "TLSA.

       Value of this RR is 52.";
    reference
      "RFC 6698";
  }

  identity HIP {
    base ianadns:data-rrtype;
    description
      "Host Identity Protocol.

       Value of this RR is 55.";
    reference
      "RFC 5205";
  }

  identity NINFO {
    base ianadns:data-rrtype;
    description
      "NINFO.

       Value of this RR is 56.";
  }

  identity RKEY {
    base ianadns:data-rrtype;
    description
      "RKEY.

       Value of this RR is 57.";
  }

  identity TALINK {
    base ianadns:data-rrtype;
    description
      "Trust Anchor LINK.

       Value of this RR is 58.";
  }

  identity CDS {
    base ianadns:data-rrtype;
    description
      "Child DS.

       Value of this RR is 59.";
    reference
      "RFC 7344";
  }

  identity CDNSKEY {
    base ianadns:data-rrtype;
    description
      "DNSKEY(s) the Child wants reflected in DS.

       Value of this RR is 60.";
    reference
      "RFC 7344";
  }

  identity OPENPGPKEY {
    base ianadns:data-rrtype;
    description
      "OpenPGP Key.

       Value of this RR is 61.";
  }

  identity CSYNC {
    base ianadns:data-rrtype;
    description
      "Child-To-Parent Synchronization.

       Value of this RR is 62.";
    reference
      "RFC 7477";
  }

  identity SPF {
    base ianadns:data-rrtype;
    description
      "Value of this RR is 99.";
    reference
      "RFC 7208";
  }

  identity UINFO {
    base ianadns:data-rrtype;
    description
      "Value of this RR is 100.";
  }

  identity UID {
    base ianadns:data-rrtype;
    description
      "Value of this RR is 101.";
  }

  identity GID {
    base ianadns:data-rrtype;
    description
      "Value of this RR is 102.";
  }

  identity UNSPEC {
    base ianadns:data-rrtype;
    description
      "Value of this RR is 103.";
  }

  identity NID {
    base ianadns:data-rrtype;
    description
      "Value of this RR is 104.";
    reference
      "RFC 6742";
  }

  identity L32 {
    base ianadns:data-rrtype;
    description
      "Value of this RR is 105.";
    reference
      "RFC 6742";
  }

  identity L64 {
    base ianadns:data-rrtype;
    description
      "Value of this RR is 106.";
    reference
      "RFC 6742";
  }

  identity LP {
    base ianadns:data-rrtype;
    description
      "Value of this RR is 107.";
    reference
      "RFC 6742";
  }

  identity EUI48 {
    base ianadns:data-rrtype;
    description
      "An EUI-48 address.

       Value of this RR is 108.";
    reference
      "RFC 7043";
  }

  identity EUI64 {
    base ianadns:data-rrtype;
    description
      "An EUI-64 address.

       Value of this RR is 109.";
    reference
      "RFC 7043";
  }

  identity TKEY {
    base ianadns:q-meta-rrtype;
    description
      "Transaction Key.

       Value of this RR is 249.";
    reference
      "RFC 2930";
  }

  identity TSIG {
    base ianadns:q-meta-rrtype;
    description
      "Transaction Signature.

       Value of this RR is 250.";
    reference
      "RFC 2845";
  }

  identity IXFR {
    base ianadns:q-meta-rrtype;
    description
      "Incremental transfer.

       Value of this RR is 251.";
    reference
      "RFC 1995";
  }

  identity AXFR {
    base ianadns:q-meta-rrtype;
    description
      "Transfer of an entire zone.

       Value of this RR is 252.";
    reference
      "RFC 1035, RFC 5936";
  }

  identity MAILB {
    base ianadns:q-meta-rrtype;
    description
      "Mailbox-related RRs (MB, MG or MR).

       Value of this RR is 253.";
    reference
      "RFC 1035";
  }

  identity MAILA {
    base ianadns:q-meta-rrtype;
    status "obsolete";
    description
      "Mail agent RRs (obsolete – see MX).

       Value of this RR is 254.";
    reference
      "RFC 1035";
  }

  identity ANY {
    base ianadns:q-meta-rrtype;
    description
      "A request for all records the server/cache has available.

       Value of this RR is 255.";
    reference
      "RFC 1035, RFC 6895";
  }

  identity URI {
    base ianadns:data-rrtype;
    description
      "URI.

       Value of this RR is 256.";
    reference
      "RFC 7553";
  }

  identity CAA {
    base ianadns:data-rrtype;
    description
      "Certification Authority Restriction.

       Value of this RR is 257.";
    reference
      "RFC 6844";
  }

  identity TA {
    base ianadns:data-rrtype;
    description
      "DNSSEC Trust Authorities.

       Value of this RR is 32768.";
  }

  identity DLV {
    base ianadns:data-rrtype;
    description
      "DNSSEC Lookaside Validation.

       Value of this RR is 32769.";
    reference
      "RFC 4431";
  }
}
