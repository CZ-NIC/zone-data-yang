module dns-zone-rpcs {

  yang-version "1.1";

  namespace "http://www.nic.cz/ns/yang/dns-zone-rpcs";

  prefix "dnszr";

  /* Imports */

  import ietf-inet-types {
    prefix "inet";
  }

  import iana-dns-parameters {
    prefix "ianadns";
  }

  import dns-zone-common {
    prefix "dnszc";
  }

  /* Metadata */

  organization
    "CZ.NIC, z. s. p. o.";

  contact
    "Editor:   Ladislav Lhotka
               <mailto:lhotka@nic.cz>";

  description
    "This module defines RPC operations for editing DNS zones.";

  reference
    "- RFC 1035: Domain Names - Implementation and Specification.

     - Knot DNS documentation, Reading and Editing Zones,
       https://www.knot-dns.cz/docs/2.x/html/operation.html#reading-and-editing-zones";

  revision 2017-01-12 {
    description
      "Initial revision.";
  }

  /* Groupings */

  grouping zone-name {
    leaf zone {
      type inet:domain-name;
      mandatory "true";
      description
        "Name of a DNS zone.";
    }
  }

  grouping rdata-fields {
    uses dnszc:rdata-fields {
      refine "rdata-content/SOA/SOA" {
        must "derived-from-or-self(../type, 'ianadns:SOA')";
      }
      refine "rdata-content/A/A" {
        must "derived-from-or-self(../type, 'ianadns:A')";
      }
      refine "rdata-content/CNAME/CNAME" {
        must "derived-from-or-self(../type, 'ianadns:CNAME')";
      }
      refine "rdata-content/HINFO/HINFO" {
        must "derived-from-or-self(../type, 'ianadns:HINFO')";
      }
      refine "rdata-content/MB/MB" {
        must "derived-from-or-self(../type, 'ianadns:MB')";
      }
      refine "rdata-content/MD/MD" {
        must "derived-from-or-self(../type, 'ianadns:MD')";
      }
      refine "rdata-content/MF/MF" {
        must "derived-from-or-self(../type, 'ianadns:MF')";
      }
      refine "rdata-content/MG/MG" {
        must "derived-from-or-self(../type, 'ianadns:MG')";
      }
      refine "rdata-content/MINFO/MINFO" {
        must "derived-from-or-self(../type, 'ianadns:MINFO')";
      }
      refine "rdata-content/MR/MR" {
        must "derived-from-or-self(../type, 'ianadns:MR')";
      }
      refine "rdata-content/MX/MX" {
        must "derived-from-or-self(../type, 'ianadns:MX')";
      }
      refine "rdata-content/NS/NS" {
        must "derived-from-or-self(../type, 'ianadns:NS')";
      }
      refine "rdata-content/NULL/NULL" {
        must "derived-from-or-self(../type, 'ianadns:NULL')";
      }
      refine "rdata-content/PTR/PTR" {
        must "derived-from-or-self(../type, 'ianadns:PTR')";
      }
      refine "rdata-content/TXT/TXT" {
        must "derived-from-or-self(../type, 'ianadns:TXT')";
      }
      refine "rdata-content/WKS/WKS" {
        must "derived-from-or-self(../type, 'ianadns:WKS')";
      }
      refine "rdata-content/AAAA/AAAA" {
        must "derived-from-or-self(../type, 'ianadns:AAAA')";
      }
      refine "rdata-content/DNSKEY/DNSKEY" {
        must "derived-from-or-self(../type, 'ianadns:DNSKEY')";
      }
      refine "rdata-content/NSEC/NSEC" {
        must "derived-from-or-self(../type, 'ianadns:NSEC')";
      }
      refine "rdata-content/DS/DS" {
        must "derived-from-or-self(../type, 'ianadns:DS')";
      }
      refine "rdata-content/NSEC3/NSEC3" {
        must "derived-from-or-self(../type, 'ianadns:NSEC3')";
      }
      refine "rdata-content/NSEC3PARAM/NSEC3PARAM" {
        must "derived-from-or-self(../type, 'ianadns:NSEC3PARAM')";
      }
      refine "rdata-content/TLSA/TLSA" {
        must "derived-from-or-self(../type, 'ianadns:TLSA')";
      }
      refine "rdata-content/IPSECKEY/IPSECKEY" {
        must "derived-from-or-self(../type, 'ianadns:IPSECKEY')";
      }
      refine "rdata-content/DNAME/DNAME" {
        must "derived-from-or-self(../type, 'ianadns:DNAME')";
      }
      refine "rdata-content/SSHFP/SSHFP" {
        must "derived-from-or-self(../type, 'ianadns:SSHFP')";
      }
      augment "rdata-content" {
        uses dnszc:rrsig-data {
          refine "RRSIG" {
            must "derived-from-or-self(../type, 'ianadns:RRSIG')";
          }
        }
      }
    }
  }

  /* RPC operations */

  rpc begin-transaction {
    description
      "Begin a zone-editing transaction.";
  }

  rpc commit-transaction {
    description
      "Commit the open zone-editing transaction.";
  }

  rpc abort-transaction {
    description
      "Abort the open zone-editing transaction.";
  }

  rpc zone-set {
    description
      "Add a specific resource record to a zone.";
    input {
      uses zone-name;
      uses dnszc:common-rr-data;
      uses rdata-fields;
    }
  }

  rpc zone-unset {
    description
      "Remove all resource records with a specific owner, RRSet or
       data.";
    input {
      uses zone-name;
      uses dnszc:owner-field;
      uses dnszc:type-field;
      uses rdata-fields;
    }
  }
}
