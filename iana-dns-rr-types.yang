module iana-dns-rr-types {

  namespace "http://www.nic.cz/ns/yang/iana-dns-rr-types";

  prefix "ianadns";

  organization
    "CZ.NIC, z. s. p. o.";

  contact
    "Editor:   Ladislav Lhotka
               <mailto:lhotka@nic.cz>";

  description
    "This module provides several data types that are used in DNS
     Resource Records.";

  reference
    "RFC 6195: Domain Name System (DNS) IANA Considerations.";

  revision 2015-08-11 {
    description
      "Initial revision.";
  }

  typedef dns-rr-class {
    type enumeration {
      enum IN {
        value "1";
        description
          "Internet";
      }
      enum CH {
        value "3";
        description
          "Chaos";
        reference
          "Moon, D., \"Chaosnet\", A.I. Memo 628, Massachusetts
           Institute of Technology Artificial Intelligence
           Laboratory, June 1981.";
      }
      enum HS {
        value "4";
        description
          "Hesiod";
        reference
          "Dyer, S., and F. Hsu, \"Hesiod\", Project Athena Technical
           Plan - Name Service, April 1987.";
      }
      enum NONE {
        value "254";
        description
          "QCLASS NONE - only meaningful in queries";
        reference
          "RFC 2136: Dynamic Updates in the Domain Name System (DNS
           UPDATE)";
      }
      enum ANY {
        value "255";
        description
          "QCLASS * (ANY) - only meaningful in queries";
        reference
          "RFC 1035: Domain Names - Implementation and
           Specification";
      }
    }
    description
      "DNS RR classes.";
  }

  identity dns-rrtype {
    description
      "Base identity from which DNS RR types are derived.";
  }
}
